Tftp2 DEFINITIONS AUTOMATIC TAGS ::= BEGIN

  Modo ::= ENUMERATED {
    octet (0),
    netascii (1),
    mail (2)
  }
  
  Transfer ::= SEQUENCE {
    filename PrintableString,
    modo Modo 
  }

  Data ::= SEQUENCE {
    blocknum INTEGER,
    body OCTET STRING (SIZE(0..512))
  }

  Ack ::= SEQUENCE {
    blocknum INTEGER
  }  

  ErrorCode ::= ENUMERATED {
    undefined (0),
    fileNotFound (1),
    accessViolation (2),
    notEnoughSpace (3),
    illegalOperation (4),
    unknownTID (5),
    fileExists (6),
    unknownUser (7)
  }
  

  Err ::= SEQUENCE {
    code ErrorCode,
    descr VisibleString
  }

  PathMsg ::= VisibleString
  
  Pasta ::= VisibleString

  Arquivo ::= SEQUENCE {
    nome VisibleString,
    tamanho INTEGER
  }

  ListItem ::= CHOICE {
      arq Arquivo,
      dir Pasta
  }

  ListResponse ::= SEQUENCE {
    itens SEQUENCE OF ListItem
  }

  MOVE ::= SEQUENCE {
    src VisibleString,
    dest VisibleString OPTIONAL
  }

  MensagemTftp ::= CHOICE {
      rrq Transfer,
      wrq Transfer,
      data Data,
      ack Ack, 
      err Err,
      list PathMsg,
      listResp ListResponse,
      mkdir PathMsg,
      move MOVE
  }
END
